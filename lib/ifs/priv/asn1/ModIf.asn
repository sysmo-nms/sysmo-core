ModIf DEFINITIONS EXPLICIT TAGS ::=

BEGIN

Groups      ::= SEQUENCE OF Group
Group       ::= PrintableString (SIZE (1..50))

AuthAck     ::= SEQUENCE {
    groups      Groups,
    staticChans SEQUENCE OF ChanInfo
}

AuthError   ::= SEQUENCE {
    error ENUMERATED {
        noShuchUser(0),
        badPass(1),
        timeout(2),
        other(3)
    },
    userId      PrintableString,
    pass        PrintableString
}

AuthResp    ::= SEQUENCE {
    userId  PrintableString,
    pass    PrintableString
}

Modules     ::= SEQUENCE OF Module
Module      ::= PrintableString (SIZE (1..30))


AuthProto   ::= ENUMERATED {localFile(0), ldap(1)}

Chan        ::= PrintableString (SIZE (1..100))
ChanInfoType    ::= ENUMERATED {create(0), delete(1), update(2)}
ChanInfo    ::= SEQUENCE {
    channel Chan,
    type    ChanInfoType
}

IfPDU ::= CHOICE {
    fromServer [0] CHOICE {
        chanInfo    [1] ChanInfo,
        authReq     [2] AuthProto,
        authAck     [3] AuthAck,
        authError   [4] AuthError,
        subscribeOk     [5] Chan,
        subscribeErr    [6] Chan,
        unsubscribeOk   [7] Chan,
        unsubscribeErr  [8] Chan,
        ...
    },
    fromClient  [1] CHOICE {
        subscribe       [0] Chan,
        unsubscribe     [1] Chan,
        authResp        [4] AuthResp,
        ...
    }
}

END
