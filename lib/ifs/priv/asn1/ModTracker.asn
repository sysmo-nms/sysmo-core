ModTracker DEFINITIONS EXPLICIT TAGS ::=
BEGIN

IpAdd   ::= PrintableString

ErlangModule    ::= PrintableString
Second          ::= INTEGER

CommandId       ::= INTEGER
CommandMsg      ::= PrintableString

GroupName       ::= PrintableString (SIZE (0..50))

TargetId        ::= PrintableString (SIZE (0..50))
TargetHostname  ::= PrintableString (SIZE (0..50))
TargetSysname   ::= PrintableString (SIZE (0..50))
TargetTags      ::= SEQUENCE OF TargetTag
TargetTag       ::= PrintableString (SIZE (0..50))
TargetProperties ::= SEQUENCE OF TargetProperty
TargetProperty  ::= PrintableString
TargetInfoType  ::= ENUMERATED {create(0), delete(1), update(2)}

ProbeId         ::= INTEGER
ProbeName       ::= PrintableString (SIZE (0..30))
ProbeMod        ::= PrintableString (SIZE (0..30))
ProbeStatus     ::= PrintableString (SIZE (0..15))
ProbeType       ::= ENUMERATED {fetch(0), status(1)}
ProbeInfoType   ::= ENUMERATED {create(0), delete(1), update(2)}
ProbeValue      ::= INTEGER
ProbeStep       ::= Second
ProbeTimeoutMax ::= INTEGER
ProbeTimeoutWait    ::= Second
ProbeInspectors ::= SEQUENCE OF ErlangModule
ProbeRRDCreate  ::= PrintableString
ProbeRRDUpdate  ::= PrintableString
ProbeRRDGraph   ::= PrintableString

RRDFile         ::= OCTET STRING

ProbeInfo   ::= SEQUENCE {
    channel     TargetId,
    probeId     ProbeId,
    name        ProbeName,
    type        ProbeType,
    probeMod    ErlangModule,
    status      ProbeStatus,
    step        ProbeStep,
    timeoutMax  ProbeTimeoutMax,
    timeoutWait ProbeTimeoutWait,
    inspectors  ProbeInspectors,
    --rrdCreate   ProbeRRDCreate,
    --rrdUpdate   ProbeRRDCreate,
    --rrdGraph    ProbeRRDCreate,
    infoType    ProbeInfoType
}
ProbeDump   ::= SEQUENCE {
    channel     TargetId,
    probeId     ProbeId,
    probeType   ProbeType,
    rrdData     RRDFile
}

-- ProbeInfo   ::= SEQUENCE {
--     channel     TargetId,
--     probe       ProbeId,
--     status      ProbeStatus,
--     name        ProbeName,
--     type        ProbeType,
--     infoType    ProbeInfoType
-- }

ProbeFetch  ::= SEQUENCE {
    channel     TargetId,
    probe       ProbeId,
    probeType   ProbeType,
    probeValue  ProbeValue
}

-- complete avec le tracker.hrl records finaux
TargetInfo  ::= SEQUENCE {
    channel     TargetId,
    hostname    TargetHostname,
    ipAdd       IpAdd,
    tags        TargetTags,
    properties  TargetProperties,
    type        TargetInfoType
}

CommandResponce ::= SEQUENCE {
    cmdId       CommandId,
    cmdMsg      CommandMsg
}

-- FROM CLIENT
TargetCreate    ::= SEQUENCE {
    ipAdd       IpAdd,
    hostname    TargetHostname,
    sysName     TargetSysname,
    gread       GroupName,
    gwrite      GroupName,
    cmdId       CommandId
}

TargetUpdate    ::= SEQUENCE {
    target      TargetId
}

TargetDelete    ::= SEQUENCE {
    target      TargetId
}

ProbeCreate     ::= SEQUENCE {
    target      TargetId,
    probeMod    ProbeMod
}

ProbeUpdate     ::= SEQUENCE {
    target      TargetId,
    probe       ProbeId
}

ProbeDelete     ::= SEQUENCE {
    target      TargetId,
    probe       ProbeId
}

-- FULL PDU
TrackerPDU ::= CHOICE {
    fromServer  [0] CHOICE {
        targetInfo  [1] TargetInfo,
        probeInfo   [2] ProbeInfo,
        probeFetch  [3] ProbeFetch,
        probeDump   [4] ProbeDump,
        cmdResp     [5] CommandResponce
    },
    fromClient  [1] CHOICE {
        createTarget    [1] TargetCreate,
        updateTarget    [2] TargetUpdate,
        deleteTarget    [3] TargetDelete,
        createProbe     [4] ProbeCreate,
        updateProbe     [5] ProbeUpdate,
        deleteProbe     [6] ProbeDelete
    }
}

END
