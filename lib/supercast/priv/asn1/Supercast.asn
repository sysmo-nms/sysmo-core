Supercast DEFINITIONS IMPLICIT TAGS ::=

BEGIN

Groups      ::= SEQUENCE OF Group
Group       ::= PrintableString (SIZE (1..50))

AuthAck     ::= SEQUENCE {
    groups      Groups,
    staticChans SEQUENCE OF ChanInfo
}

AuthError   ::= SEQUENCE {
    error ENUMERATED {
        noShuchUser(0),
        badPass(1),
        timeout(2),
        other(3)
    },
    userId      PrintableString,
    pass        PrintableString
}

AuthResp    ::= SEQUENCE {
    userId  PrintableString,
    pass    PrintableString
}

ServerInfo ::= SEQUENCE {
    authType    PrintableString,
    dataPort    INTEGER,
    dataProto   PrintableString
}

Chan        ::= PrintableString (SIZE (1..100))
ChanInfoType    ::= ENUMERATED {create(0), delete(1), update(2)}
ChanInfo    ::= SEQUENCE {
    channel Chan,
    type    ChanInfoType
}

-- SUBSCRIBE AND UNSUBSCRIBE
-- from client
Subscribe   ::= SEQUENCE {
    queryId INTEGER,
    chan    Chan
}

Unsubscribe ::= SEQUENCE {
    queryId INTEGER,
    chan    Chan
}

--from server
SubscribeOk   ::= SEQUENCE {
    queryId INTEGER,
    chan    Chan
}

SubscribeErr   ::= SEQUENCE {
    queryId INTEGER,
    chan    Chan
}

UnsubscribeOk ::= SEQUENCE {
    queryId INTEGER,
    chan    Chan
}

UnsubscribeErr ::= SEQUENCE {
    queryId INTEGER,
    chan    Chan
}

SupercastPDU ::= CHOICE {
    fromServer [0] CHOICE {
        chanInfo        [1] ChanInfo,
        serverInfo      [2] ServerInfo,
        authAck         [3] AuthAck,
        authError       [4] AuthError,
        subscribeOk     [5] SubscribeOk,
        subscribeErr    [6] SubscribeErr,
        unsubscribeOk   [7] UnsubscribeOk,
        unsubscribeErr  [8] UnsubscribeErr,
        ...
    },
    fromClient  [1] CHOICE {
        subscribe       [0] Subscribe,
        unsubscribe     [1] Unsubscribe,
        authResp        [4] AuthResp,
        ...
    }
}

END
