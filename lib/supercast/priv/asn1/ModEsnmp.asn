ModEsnmp DEFINITIONS EXPLICIT TAGS ::=
BEGIN

TrapsTableRow   ::= SEQUENCE {
    timeStamp   [0] PrintableString,
    version     [1] PrintableString,
    fromIp      [2] PrintableString,
    fromPort    [3] PrintableString,
    credentials [4] PrintableString,
    tags        [5] PrintableString,
    message     [6] PrintableString
}

FromServer ::= CHOICE {
    trap            [0] SEQUENCE OF TrapsTableRow
}

EsnmpPDU    ::= CHOICE {
    fromServer  [0] FromServer
}

END
