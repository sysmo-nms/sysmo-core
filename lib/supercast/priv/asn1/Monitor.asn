Monitor DEFINITIONS IMPLICIT TAGS ::=
BEGIN

IMPORTS
    LoggerRrdDump             FROM MonitorLoggerRrd
    LoggerRrdEvent            FROM MonitorLoggerRrd
    ExtendedReply             FROM MonitorExtendedQuery
    ExtendedQueryFromClient   FROM MonitorExtendedQuery;

-- BASIC TYPES --
ErlangModule    ::= PrintableString
Second          ::= INTEGER
MicroSecond     ::= INTEGER
GroupName       ::= PrintableString (SIZE (0..50))
TargetId        ::= PrintableString (SIZE (0..50))
InfoTargetType  ::= ENUMERATED {create(0), delete(1), update(2)}
ProbeName       ::= PrintableString (SIZE (0..30))
ProbeStatus     ::= PrintableString (SIZE (0..15))
InfoProbeType   ::= ENUMERATED {create(0), delete(1), update(2)}

IpInfo          ::= SEQUENCE {
    version     PrintableString,
    stringVal   PrintableString
}

-- SEQUENCE TYPES --
---------------------------------------
-- FROM SERVER
---------------------------------------

-- PermConf
PermConf        ::= SEQUENCE {
    read        SEQUENCE OF GroupName,
    write       SEQUENCE OF GroupName
}

-- Properties --
Property    ::= SEQUENCE {
    key     PrintableString,
    value   PrintableString
}
Properties  ::= SEQUENCE OF Property

-- Inspectors --
Inspector   ::= SEQUENCE {
    module  ErlangModule,
    conf    PrintableString
}
Inspectors  ::= SEQUENCE OF Inspector

---------------------------------------
-- Loggers ----------------------------
---------------------------------------
-- RRD --
LoggerRrd2   ::= SEQUENCE {
    module      ErlangModule,
    type        PrintableString,
    rrdCreate   PrintableString,
    rrdUpdate   PrintableString,
    rrdGraphs   SEQUENCE OF PrintableString,
    indexes     SEQUENCE OF INTEGER
}

Logger  ::= CHOICE {
    loggerRrd2      [3] LoggerRrd2
}

Loggers     ::= SEQUENCE OF Logger

-- InfoProbe
InfoProbe   ::= SEQUENCE {
    channel     TargetId,
    name        ProbeName,
    descr       PrintableString,
    info        PrintableString,
    permissions PermConf,
    probeMod    ErlangModule,
    probeConf   PrintableString,
    status      ProbeStatus,
    timeout     Second,
    step        Second,
    inspectors  Inspectors,
    loggers     Loggers,
    properties  Properties,
    active      INTEGER,
    infoType    InfoProbeType
}

-- Target info
InfoTarget  ::= SEQUENCE {
    channel         TargetId,
    properties      Properties,
    sysProperties   Properties,
    type            InfoTargetType
}

-- ProbeReturn 
ProbeReturn ::= SEQUENCE {
    target          TargetId,
    probeId         PrintableString,
    status          ProbeStatus,
    originalReply   PrintableString,
    timestamp       MicroSecond,
    keysVals        Properties,
    nextReturn      MicroSecond
}

DeleteProbe ::= SEQUENCE {
    target      PrintableString,
    probe       PrintableString
}
---------------------------------------
-- FULL PDU
---------------------------------------
MonitorPDU ::= CHOICE {
    fromServer  [0] CHOICE {
        infoTarget      [1] InfoTarget,
        infoProbe       [2] InfoProbe,
        probeReturn     [3] ProbeReturn,
        --infoJob       
        --infoDependency

        deleteTarget     [5] PrintableString,
        deleteProbe      [6] DeleteProbe,
        --deleteJob        [7] PrintableString,
        --deleteDependency [8] PrintableString,


        extendedReply [12] ExtendedReply,

        loggerRrdDump   [20] LoggerRrdDump,
        loggerRrdEvent  [21] LoggerRrdEvent
    },
    fromClient  [1] CHOICE {
        extendedQueryFromClient [20] ExtendedQueryFromClient
    }
}

END
