ModMonitor DEFINITIONS IMPLICIT TAGS ::=
BEGIN

IMPORTS
    LoggerRrdDump  FROM MonitorLoggerRrd
    LoggerRrdEvent FROM MonitorLoggerRrd;

-- BASIC TYPES --
QueryId         ::= INTEGER
ErlangModule    ::= PrintableString
Second          ::= INTEGER
MicroSecond     ::= INTEGER
GroupName       ::= PrintableString (SIZE (0..50))
TargetId        ::= PrintableString (SIZE (0..50))
TargetInfoType  ::= ENUMERATED {create(0), delete(1), update(2)}
ProbeName       ::= PrintableString (SIZE (0..30))
ProbeStatus     ::= PrintableString (SIZE (0..15))
ProbeType       ::= ENUMERATED {fetch(0), status(1)}
ProbeInfoType   ::= ENUMERATED {create(0), delete(1), update(2)}

IpInfo          ::= SEQUENCE {
    version     PrintableString,
    stringVal   PrintableString
}

-- SEQUENCE TYPES --
---------------------------------------
-- FROM SERVER
---------------------------------------

-- PermConf
PermConf        ::= SEQUENCE {
    read        SEQUENCE OF GroupName,
    write       SEQUENCE OF GroupName
}

-- Properties --
Property    ::= SEQUENCE {
    key     PrintableString,
    value   PrintableString
}
Properties  ::= SEQUENCE OF Property

-- Inspectors --
Inspector   ::= SEQUENCE {
    module  ErlangModule,
    conf    PrintableString
}
Inspectors  ::= SEQUENCE OF Inspector

---------------------------------------
-- Loggers ----------------------------
---------------------------------------
-- RRD --
LoggerRrd2   ::= SEQUENCE {
    module      ErlangModule,
    type        PrintableString,
    rrdCreate   PrintableString,
    rrdUpdate   PrintableString,
    rrdGraphs   SEQUENCE OF PrintableString,
    indexes     SEQUENCE OF INTEGER
}

-- Text --
LoggerText  ::= SEQUENCE {
    module  ErlangModule,
    conf    PrintableString
}

-- Events --
LoggerEvents ::= SEQUENCE {
    module  ErlangModule,
    conf    PrintableString
}

Logger  ::= CHOICE {
    loggerText      [1] LoggerText,
    loggerEvents    [2] LoggerEvents,
    loggerRrd2      [3] LoggerRrd2
}
Loggers     ::= SEQUENCE OF Logger

-- ProbeInfo
ProbeConf       ::= SEQUENCE {
    name        ProbeName,
    type        ProbeType
}

FileData        ::= OCTET STRING

ProbeInfo   ::= SEQUENCE {
    channel     TargetId,
    name        ProbeName,
    descr       PrintableString,
    info        PrintableString,
    permissions PermConf,
    probeMod    ErlangModule,
    probeConf   PrintableString,
    status      ProbeStatus,
    timeout     Second,
    step        Second,
    inspectors  Inspectors,
    loggers     Loggers,
    properties  Properties,
    active      INTEGER,
    infoType    ProbeInfoType
}

-- ProbeEvent
ProbeEvent      ::= SEQUENCE {
    probeName   PrintableString,
    eventId     INTEGER,
    insertTs    MicroSecond,
    ackTs       MicroSecond,
    status      ProbeStatus,
    textual     PrintableString,
    ackNeeded   BOOLEAN,
    ackValue    PrintableString,
    groupOwner  PrintableString,
    userOwner   PrintableString
}

-- ProbeReturn 
ProbeReturn ::= SEQUENCE {
    target          TargetId,
    probeId         PrintableString,
    status          ProbeStatus,
    originalReply   PrintableString,
    timestamp       MicroSecond,
    keysVals        Properties,
    nextReturn      MicroSecond
}

TargetInfo  ::= SEQUENCE {
    channel     TargetId,
    properties  Properties,
    type        TargetInfoType
}

---------------------------------------
-- FROM CLIENT
---------------------------------------
CreateTarget    ::= SEQUENCE {
    ipAdd       PrintableString,
    permConf    PermConf,
    staticName  PrintableString,
    snmpv2ro    PrintableString,
    snmpv2rw    PrintableString,
    template    PrintableString,
    queryId     QueryId
}

CreateSimpleProbe     ::= SEQUENCE {
    target      TargetId,
    name        PrintableString,
    description PrintableString,
    permConf    PermConf,
    template    PrintableString,
    timeout     INTEGER,
    step        INTEGER,
    flags       Properties,
    exe         PrintableString,
    queryId     QueryId
}

QueryType       ::= ENUMERATED {
    getChecksInfo(0)
}

Query           ::= SEQUENCE {
    queryId     QueryId,
    query       PrintableString
}

Arg             ::= SEQUENCE {
    flag        PrintableString,
    value       PrintableString
}

SimulateCheck   ::= SEQUENCE {
    queryId     QueryId,
    executable  PrintableString,
    args        SEQUENCE OF Arg
}

-- TODO server API
UpdateTarget    ::= SEQUENCE {
    target      TargetId
}

DeleteTarget    ::= SEQUENCE {
    target      TargetId
}

MonitorReply    ::= SEQUENCE {
    queryId     QueryId,
    status      BOOLEAN,
    info        PrintableString
}

GetCheckReply   ::= SEQUENCE {
    queryId     QueryId,
    status      BOOLEAN,
    infos       SEQUENCE OF OCTET STRING
}



-------------------------------------------------------------------------------
-- EXTENDED QUERY/REPLY
-------------------------------------------------------------------------------
SnmpElementInfoQuery ::= SEQUENCE {
    ip            IpInfo,
    port          INTEGER,
    timeout       INTEGER,
    snmpVer       PrintableString,
    community     PrintableString,
    v3SecLevel    PrintableString,
    v3User        PrintableString,
    v3AuthAlgo    PrintableString,
    v3AuthKey     PrintableString,
    v3PrivAlgo    PrintableString,
    v3PrivKey     PrintableString
}

SnmpElementCreateQuery ::= SEQUENCE {
    ip            IpInfo,
    port          INTEGER,
    timeout       INTEGER,
    snmpVer       PrintableString,
    community     PrintableString,
    v3SecLevel    PrintableString,
    v3User        PrintableString,
    v3AuthAlgo    PrintableString,
    v3AuthKey     PrintableString,
    v3PrivAlgo    PrintableString,
    v3PrivKey     PrintableString,
    ifSelection   SEQUENCE OF INTEGER
}

ExtendedQuery   ::= CHOICE {
    snmpElementInfoQuery    [0] SnmpElementInfoQuery,
    snmpElementCreateQuery  [1] SnmpElementCreateQuery
}

ExtendedQueryMsg   ::= SEQUENCE {
    queryId     QueryId,
    query       ExtendedQuery
}

ReplyChoice   ::= CHOICE {
    string              [0] PrintableString,
    snmpSystemInfo      [1] SnmpSystemInfo,
    snmpInterfacesInfo  [2] SEQUENCE OF SnmpInterfaceInfo
}

ExtendedReplyMsg   ::= SEQUENCE {
    queryId     QueryId,
    status      BOOLEAN,
    lastPdu     BOOLEAN,
    reply       ReplyChoice
}

SnmpSystemInfo  ::= SEQUENCE {
    sysDescr        PrintableString,
    sysObjectId     PrintableString,
    sysUpTime       PrintableString,
    sysContact      PrintableString,
    sysName         PrintableString,
    sysLocation     PrintableString,
    sysServices     INTEGER,
    sysORLastChange PrintableString
}

SnmpInterfaceInfo ::= SEQUENCE {
    ifIndex         INTEGER,
    ifDescr         PrintableString,
    ifType          INTEGER,
    ifMTU           INTEGER,
    ifSpeed         INTEGER,
    ifPhysAddress   PrintableString,
    ifAdminStatus   INTEGER,
    ifOperStatus    INTEGER,
    ifLastChange    PrintableString
}
-------------------------------------------------------------------------------
-- EXTENDED QUERY/REPLY END
-------------------------------------------------------------------------------



---------------------------------------
-- FULL PDU
---------------------------------------
MonitorPDU ::= CHOICE {
    fromServer  [0] CHOICE {
        targetInfo      [1] TargetInfo,
        probeInfo       [2] ProbeInfo,
        probeReturn     [3] ProbeReturn,

        monitorReply    [10] MonitorReply,
        getCheckReply   [11] GetCheckReply,
        extendedReplyMsg [12] ExtendedReplyMsg,

        loggerRrdDump   [20] LoggerRrdDump,
        loggerRrdEvent  [21] LoggerRrdEvent
    },
    fromClient  [1] CHOICE {
        createTarget    [1] CreateTarget,
        updateTarget    [2] UpdateTarget,
        deleteTarget    [3] DeleteTarget,
        createSimpleProbe   [4] CreateSimpleProbe,
        simulateCheck   [7] SimulateCheck,
        -- simple queries only include a QueryId
        query           [10] Query,
        extendedQueryMsg [20] ExtendedQueryMsg
    }
}

END
