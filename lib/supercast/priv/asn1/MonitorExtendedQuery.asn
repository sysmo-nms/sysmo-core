MonitorExtendedQuery DEFINITIONS IMPLICIT TAGS ::=

BEGIN

IpInfo          ::= SEQUENCE {
    version     PrintableString,
    stringVal   PrintableString
}


-- ----------
-- QUERIES --
-- ----------
SnmpElementInfoQuery ::= SEQUENCE {
    ip            IpInfo,
    port          INTEGER,
    timeout       INTEGER,
    snmpVer       PrintableString,
    community     PrintableString,
    v3SecLevel    PrintableString,
    v3User        PrintableString,
    v3AuthAlgo    PrintableString,
    v3AuthKey     PrintableString,
    v3PrivAlgo    PrintableString,
    v3PrivKey     PrintableString
}

SnmpElementCreateQuery ::= SEQUENCE {
    ip            IpInfo,
    port          INTEGER,
    timeout       INTEGER,
    snmpVer       PrintableString,
    community     PrintableString,
    v3SecLevel    PrintableString,
    v3User        PrintableString,
    v3AuthAlgo    PrintableString,
    v3AuthKey     PrintableString,
    v3PrivAlgo    PrintableString,
    v3PrivKey     PrintableString,
    ifSelection   SEQUENCE OF INTEGER
}

Prop ::= SEQUENCE {
    key PrintableString,
    val PrintableString
}

ElementInterfaceQuery ::= SEQUENCE {
    sysProperties   SEQUENCE OF Prop,
    properties      SEQUENCE OF Prop
}

CreateTargetQuery ::= SEQUENCE {
    sysProperties   SEQUENCE OF Prop,
    properties      SEQUENCE OF Prop
}

CreateNchecksQuery ::= SEQUENCE {
    target  PrintableString,
    type    PrintableString,
    conf    SEQUENCE OF Prop
}

CreateIfPerfQuery ::= SEQUENCE {
    target      PrintableString,
    interfaces  SEQUENCE OF INTEGER
}

ExtendedQuery ::= CHOICE {
    snmpElementInfoQuery    [0] SnmpElementInfoQuery,
    snmpElementCreateQuery  [1] SnmpElementCreateQuery,

    createTargetQuery       [10] CreateTargetQuery,
    elementInterfaceQuery   [11] ElementInterfaceQuery,
    createNchecksQuery      [12] CreateNchecksQuery,
    createIfPerfQuery       [13] CreateIfPerfQuery,

    deleteProbeQuery        [20] PrintableString,
    deleteTargetQuery       [21] PrintableString,

    forceProbeQuery         [30] PrintableString
}


ExtendedQueryFromClient   ::= SEQUENCE {
    queryId     INTEGER,
    query       ExtendedQuery
}

-- ----------
-- REPLIES --
-- ----------
SnmpSystemInfo  ::= SEQUENCE {
    sysDescr        PrintableString,
    sysObjectId     PrintableString,
    sysUpTime       PrintableString,
    sysContact      PrintableString,
    sysName         PrintableString,
    sysLocation     PrintableString,
    sysServices     INTEGER,
    sysORLastChange PrintableString
}

SnmpInterfaceInfo ::= SEQUENCE {
    ifIndex         INTEGER,
    ifDescr         PrintableString,
    ifType          INTEGER,
    ifMTU           INTEGER,
    ifSpeed         INTEGER,
    ifPhysAddress   PrintableString,
    ifAdminStatus   INTEGER,
    ifOperStatus    INTEGER,
    ifLastChange    PrintableString
}

ReplyChoice   ::= CHOICE {
    string              [0] PrintableString,
    snmpSystemInfo      [1] SnmpSystemInfo,
    snmpInterfacesInfo  [2] SEQUENCE OF SnmpInterfaceInfo
}

ExtendedReply   ::= SEQUENCE {
    queryId     INTEGER,
    status      BOOLEAN,
    lastPdu     BOOLEAN,
    reply       ReplyChoice
}

END
