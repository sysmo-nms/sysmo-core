ModEsnmp DEFINITIONS EXPLICIT TAGS ::=
BEGIN

TrapsTableRow   ::= SEQUENCE {
    timeStamp   PrintableString,
    version     PrintableString,
    fromIp      PrintableString,
    fromPort    PrintableString,
    credentials PrintableString,
    tags        PrintableString,
    message     PrintableString
}

IpAddr  ::= SEQUENCE {
    o1  INTEGER,
    o2  INTEGER,
    o3  INTEGER,
    o4  INTEGER
}

AgentConf  ::= SEQUENCE {
    targetName      PrintableString,
    community       PrintableString,
    ipAddr          IpAddr,
    port            INTEGER,
    engineID        PrintableString,
    timeout         INTEGER,
    maxMessageSize  INTEGER,
    version         PrintableString,
    secModel        PrintableString,
    secName         PrintableString,
    secLevel        PrintableString
}

FromServer ::= CHOICE {
    trap            [0] SEQUENCE OF TrapsTableRow,
    agentsConf      [1] SEQUENCE OF AgentConf
}

FromClient ::= CHOICE {
    registerV2Agent [0] AgentConf
}

EsnmpPDU    ::= CHOICE {
    fromServer  [0] FromServer,
    fromClient  [1] FromClient
}

END
