ModIf DEFINITIONS EXPLICIT TAGS ::=

BEGIN

Groups      ::= SEQUENCE OF Group
Group       ::= PrintableString (SIZE (1..50))

Modules     ::= SEQUENCE OF Module
Module      ::= PrintableString (SIZE (1..30))
Channels    ::= SEQUENCE OF Channel
Channel     ::= PrintableString (SIZE (1..30))

AuthProto   ::= ENUMERATED {localFile(0), ldap(1)}

ChanInfo    ::= SEQUENCE {module Module, channel Channel}

IfPDU ::= CHOICE {
    fromServer [0] CHOICE {
        chanInfo    [1] ChanInfo,
        authReq     [2] AuthProto,
        authAck     [3] SEQUENCE {
                groups  Groups,
                modules Modules
        },
        authError   [4] SEQUENCE {
            error       ENUMERATED {
                    noShuchUser(0),
                    badPass(1),
                    timeout(2),
                    other(3)
            },
            userId      PrintableString,
            pass        PrintableString
        },
        subscribeOk [5] Module,
        unsubscribeOk [6] Module,
        ...
    },
    fromClient  [1] CHOICE {
        subscribe   [0] Module,
        unsubscribe [1] Module,
        authResp    [4] SEQUENCE {
                userId  PrintableString,
                pass    PrintableString
        },
        ...
    }
}

END
